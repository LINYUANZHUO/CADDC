;;; =====================================================================
;;;  Socket86.lsp --- 86 型插座图块: 一键连续插入
;;;  图形来源: 先生提供的 3孔5孔插座.dxf (1:1 提取, 未缩放, 颜色归一为随层)
;;; ---------------------------------------------------------------------
;;;  命令: CC
;;;    敲 CC 之后直接在图上点插入点 -> 连续插入 86x86 插座块,
;;;    插入点就是外框的 **左下角**; 一直点一直插, 按 ESC(或回车) 退出。
;;;
;;;    想画三孔: 在"指定插入点"那一步输 S  ->  之后改画三孔插座,
;;;              再输一次 S 可切回五孔。当前模式一直写在提示行最前面。
;;;
;;;  图块(首次使用时自动创建, 无需自己画):
;;;    CC-86五孔插座 : 86x86 直角外框 + 面板 + 5 孔
;;;    CC-86三孔插座 : 86x86 直角外框 + 面板 + 3 孔
;;;    外框是直角矩形(无圆弧), 四个角都是端点, 插入时捕捉方便;
;;;    块内图元画在 0 层且颜色随层 -> 插入后自动跟随当前图层的颜色/线型。
;;;
;;;  说明: 建块与插入都用 entmake 直接写实体, 不走 -INSERT 命令,
;;;        所以命令行不刷提示、不闪屏、也没有命令回显。
;;; =====================================================================


;;; ---------------------------------------------------------------------
;;;  块图形 (由 dxf_to_lsp.py 自动生成, 手改请改生成脚本)
;;; ---------------------------------------------------------------------

;; 五孔: 外框 + 面板 + 5 孔
(defun cc:Geom5 ()
    (entmake '((0 . "LWPOLYLINE") (100 . "AcDbEntity") (8 . "0") (100 . "AcDbPolyline")
      (90 . 4) (70 . 1)
       (10 0 86) (10 86 86) (10 86 0) (10 0 0)
    ))
    (entmake '((0 . "LWPOLYLINE") (100 . "AcDbEntity") (8 . "0") (100 . "AcDbPolyline")
      (90 . 4) (70 . 1)
       (10 18.426 9.595) (10 67.574 9.595) (10 67.574 76.405) (10 18.426 76.405)
    ))
    (entmake '((0 . "LWPOLYLINE") (100 . "AcDbEntity") (8 . "0") (100 . "AcDbPolyline")
      (90 . 4) (70 . 1)
       (10 39.011 22.881) (10 37.498 21.998) (10 33.917 28.141) (10 35.431 29.023)
    ))
    (entmake '((0 . "LINE") (100 . "AcDbEntity") (8 . "0") (100 . "AcDbLine") (10 36.187 68.689 0.0) (11 37.699 68.689 0.0)))
    (entmake '((0 . "LINE") (100 . "AcDbEntity") (8 . "0") (100 . "AcDbLine") (10 37.699 61.663 0.0) (11 36.187 61.663 0.0)))
    (entmake '((0 . "LINE") (100 . "AcDbEntity") (8 . "0") (100 . "AcDbLine") (10 36.187 61.663 0.0) (11 36.187 68.689 0.0)))
    (entmake '((0 . "LINE") (100 . "AcDbEntity") (8 . "0") (100 . "AcDbLine") (10 37.699 68.689 0.0) (11 37.699 61.663 0.0)))
    (entmake '((0 . "LWPOLYLINE") (100 . "AcDbEntity") (8 . "0") (100 . "AcDbPolyline")
      (90 . 4) (70 . 1)
       (10 42.124 36.2) (10 43.876 36.2) (10 43.876 43.31) (10 42.124 43.31)
    ))
    (entmake '((0 . "LWPOLYLINE") (100 . "AcDbEntity") (8 . "0") (100 . "AcDbPolyline")
      (90 . 4) (70 . 1)
       (10 46.989 22.881) (10 48.502 21.998) (10 52.083 28.141) (10 50.569 29.023)
    ))
    (entmake '((0 . "LINE") (100 . "AcDbEntity") (8 . "0") (100 . "AcDbLine") (10 49.813 68.689 0.0) (11 48.301 68.689 0.0)))
    (entmake '((0 . "LINE") (100 . "AcDbEntity") (8 . "0") (100 . "AcDbLine") (10 48.301 68.689 0.0) (11 48.301 61.663 0.0)))
    (entmake '((0 . "LINE") (100 . "AcDbEntity") (8 . "0") (100 . "AcDbLine") (10 48.301 61.663 0.0) (11 49.813 61.663 0.0)))
    (entmake '((0 . "LINE") (100 . "AcDbEntity") (8 . "0") (100 . "AcDbLine") (10 49.813 61.663 0.0) (11 49.813 68.689 0.0)))
)

;; 三孔: 外框 + 面板 + 3 孔
(defun cc:Geom3 ()
    (entmake '((0 . "LWPOLYLINE") (100 . "AcDbEntity") (8 . "0") (100 . "AcDbPolyline")
      (90 . 4) (70 . 1)
       (10 0 86) (10 86 86) (10 86 0) (10 0 0)
    ))
    (entmake '((0 . "LWPOLYLINE") (100 . "AcDbEntity") (8 . "0") (100 . "AcDbPolyline")
      (90 . 4) (70 . 1)
       (10 18.426 9.685) (10 67.574 9.685) (10 67.574 76.495) (10 18.426 76.495)
    ))
    (entmake '((0 . "LWPOLYLINE") (100 . "AcDbEntity") (8 . "0") (100 . "AcDbPolyline")
      (90 . 4) (70 . 1)
       (10 39.011 32.894) (10 37.498 32.012) (10 33.917 38.154) (10 35.431 39.036)
    ))
    (entmake '((0 . "LWPOLYLINE") (100 . "AcDbEntity") (8 . "0") (100 . "AcDbPolyline")
      (90 . 4) (70 . 1)
       (10 42.124 46.214) (10 43.876 46.214) (10 43.876 53.324) (10 42.124 53.324)
    ))
    (entmake '((0 . "LWPOLYLINE") (100 . "AcDbEntity") (8 . "0") (100 . "AcDbPolyline")
      (90 . 4) (70 . 1)
       (10 46.989 32.894) (10 48.502 32.012) (10 52.083 38.154) (10 50.569 39.036)
    ))
)


;;; ---------------------------------------------------------------------
;;;  建块 / 插入
;;; ---------------------------------------------------------------------

;; 建块: 已存在就直接用(不重复定义), 返回块名
;; 基点 = 0,0,0  ->  插入时以外框左下角为插入点
(defun cc:Define (name kind)
  (if (not (tblsearch "BLOCK" name))
    (progn
      (entmake (list '(0 . "BLOCK")
                     '(100 . "AcDbEntity")
                     '(8 . "0")
                     '(100 . "AcDbBlockBegin")
                     (cons 2 name)
                     '(70 . 0)
                     '(10 0.0 0.0 0.0)
                     (cons 3 name)))
      (if (= kind 3) (cc:Geom3) (cc:Geom5))
      (entmake '((0 . "ENDBLK")
                 (100 . "AcDbEntity")
                 (8 . "0")
                 (100 . "AcDbBlockEnd")))
    )
  )
  name
)

;; 插入: 直接 entmake 一个块参照, 不走 -INSERT 命令(无回显, 不闪屏)
;; 块参照放在当前图层上, 于是块内 0 层图元自动跟随当前图层颜色
(defun cc:Insert (blk pt)
  (entmake (list '(0 . "INSERT")
                 '(100 . "AcDbEntity")
                 (cons 8 (getvar "CLAYER"))
                 '(100 . "AcDbBlockReference")
                 (cons 2 blk)
                 (cons 10 pt)
                 '(41 . 1.0)
                 '(42 . 1.0)
                 '(43 . 1.0)
                 '(50 . 0.0)))
)


;;; ---------------------------------------------------------------------
;;;  CC --- 连续插入插座
;;; ---------------------------------------------------------------------
(defun c:CC (/ b5 b3 three pt n5 n3)
  (setq b5 (cc:Define "CC-86五孔插座" 5)
        b3 (cc:Define "CC-86三孔插座" 3)
        three nil
        n5 0 n3 0)
  (while (progn
           (initget "S")
           (setq pt
             (getpoint
               (strcat "\n[" (if three "三孔" "五孔")
                       "] 指定插入点(外框左下角) 或 [S 改画"
                       (if three "五孔" "三孔")
                       "] <ESC 或回车 退出>: ")))
           (cond
             ;; 切换模式, 继续循环
             ((= pt "S")
              (setq three (not three))
              T)
             ;; 插入
             ((= (type pt) 'LIST)
              (if (cc:Insert (if three b3 b5) pt)
                (if three (setq n3 (1+ n3)) (setq n5 (1+ n5)))
                (princ "\n  插入失败。")
              )
              T)
             ;; 回车 / ESC -> 结束
             (T nil)
           )
         )
  )
  (princ (strcat "\n[CC] 本次共插入 五孔 " (itoa n5) " 个, 三孔 " (itoa n3) " 个。"))
  (princ)
)


;;; ---------------------------------------------------------------------
(princ "\n插座图块工具已加载:  CC = 连续插入 86x86 插座 (默认五孔, 输 S 切三孔, ESC 退出)")
(princ)
