;;; =====================================================================
;;;  Socket86.lsp --- 86 型插座 / 开关 图块: 一键连续插入
;;;  图形来源: 先生提供的 DXF (1:1 提取, 未缩放, 颜色归一为随层)
;;;    3孔5孔插座.dxf -> 五孔 / 三孔
;;;    开关.dxf       -> 单开 / 双开 / 三开
;;; ---------------------------------------------------------------------
;;;  命令: CC
;;;    敲 CC 之后直接在图上点插入点 -> 连续插入 86x86 图块,
;;;    插入点就是外框的 **左下角**; 一直点一直插, 按 ESC(或回车) 退出。
;;;
;;;    在"指定插入点"那一步可以随时换图形(当前图形写在提示行最前面):
;;;      S = 五孔 <-> 三孔 来回切
;;;      C = 单开开关     V = 双开开关     B = 三开开关
;;;
;;;  图块(首次使用时自动创建, 无需自己画):
;;;    CC-86五孔插座 : 86x86 直角外框 + 面板 + 5 孔
;;;    CC-86三孔插座 : 86x86 直角外框 + 面板 + 3 孔
;;;    CC-86单开开关 : 86x86 直角外框 + 面板 + 1 按钮
;;;    CC-86双开开关 : 86x86 直角外框 + 面板 + 2 按钮 + 分隔线
;;;    CC-86三开开关 : 86x86 直角外框 + 面板 + 3 按钮 + 分隔线
;;;    外框是直角矩形(无圆弧), 四个角都是端点, 插入时捕捉方便;
;;;    块内图元画在 0 层且颜色随层 -> 插入后自动跟随当前图层的颜色/线型。
;;;
;;;  说明: 建块与插入都用 entmake 直接写实体, 不走 -INSERT 命令,
;;;        所以命令行不刷提示、不闪屏、也没有命令回显。
;;; =====================================================================


;;; ---------------------------------------------------------------------
;;;  块图形 (由 dxf_to_lsp.py / gen_switch.py 自动生成, 手改请改生成脚本)
;;; ---------------------------------------------------------------------

;; 五孔: 外框 + 面板 + 5 孔
(defun cc:Geom5 ()
    (entmake '((0 . "LWPOLYLINE") (100 . "AcDbEntity") (8 . "0") (100 . "AcDbPolyline")
      (90 . 4) (70 . 1)
       (10 0 86) (10 86 86) (10 86 0) (10 0 0)
    ))
    (entmake '((0 . "LWPOLYLINE") (100 . "AcDbEntity") (8 . "0") (100 . "AcDbPolyline")
      (90 . 4) (70 . 1)
       (10 18.426 9.595) (10 67.574 9.595) (10 67.574 76.405) (10 18.426 76.405)
    ))
    (entmake '((0 . "LWPOLYLINE") (100 . "AcDbEntity") (8 . "0") (100 . "AcDbPolyline")
      (90 . 4) (70 . 1)
       (10 39.011 22.881) (10 37.498 21.998) (10 33.917 28.141) (10 35.431 29.023)
    ))
    (entmake '((0 . "LINE") (100 . "AcDbEntity") (8 . "0") (100 . "AcDbLine") (10 36.187 68.689 0.0) (11 37.699 68.689 0.0)))
    (entmake '((0 . "LINE") (100 . "AcDbEntity") (8 . "0") (100 . "AcDbLine") (10 37.699 61.663 0.0) (11 36.187 61.663 0.0)))
    (entmake '((0 . "LINE") (100 . "AcDbEntity") (8 . "0") (100 . "AcDbLine") (10 36.187 61.663 0.0) (11 36.187 68.689 0.0)))
    (entmake '((0 . "LINE") (100 . "AcDbEntity") (8 . "0") (100 . "AcDbLine") (10 37.699 68.689 0.0) (11 37.699 61.663 0.0)))
    (entmake '((0 . "LWPOLYLINE") (100 . "AcDbEntity") (8 . "0") (100 . "AcDbPolyline")
      (90 . 4) (70 . 1)
       (10 42.124 36.2) (10 43.876 36.2) (10 43.876 43.31) (10 42.124 43.31)
    ))
    (entmake '((0 . "LWPOLYLINE") (100 . "AcDbEntity") (8 . "0") (100 . "AcDbPolyline")
      (90 . 4) (70 . 1)
       (10 46.989 22.881) (10 48.502 21.998) (10 52.083 28.141) (10 50.569 29.023)
    ))
    (entmake '((0 . "LINE") (100 . "AcDbEntity") (8 . "0") (100 . "AcDbLine") (10 49.813 68.689 0.0) (11 48.301 68.689 0.0)))
    (entmake '((0 . "LINE") (100 . "AcDbEntity") (8 . "0") (100 . "AcDbLine") (10 48.301 68.689 0.0) (11 48.301 61.663 0.0)))
    (entmake '((0 . "LINE") (100 . "AcDbEntity") (8 . "0") (100 . "AcDbLine") (10 48.301 61.663 0.0) (11 49.813 61.663 0.0)))
    (entmake '((0 . "LINE") (100 . "AcDbEntity") (8 . "0") (100 . "AcDbLine") (10 49.813 61.663 0.0) (11 49.813 68.689 0.0)))
)

;; 三孔: 外框 + 面板 + 3 孔
(defun cc:Geom3 ()
    (entmake '((0 . "LWPOLYLINE") (100 . "AcDbEntity") (8 . "0") (100 . "AcDbPolyline")
      (90 . 4) (70 . 1)
       (10 0 86) (10 86 86) (10 86 0) (10 0 0)
    ))
    (entmake '((0 . "LWPOLYLINE") (100 . "AcDbEntity") (8 . "0") (100 . "AcDbPolyline")
      (90 . 4) (70 . 1)
       (10 18.426 9.685) (10 67.574 9.685) (10 67.574 76.495) (10 18.426 76.495)
    ))
    (entmake '((0 . "LWPOLYLINE") (100 . "AcDbEntity") (8 . "0") (100 . "AcDbPolyline")
      (90 . 4) (70 . 1)
       (10 39.011 32.894) (10 37.498 32.012) (10 33.917 38.154) (10 35.431 39.036)
    ))
    (entmake '((0 . "LWPOLYLINE") (100 . "AcDbEntity") (8 . "0") (100 . "AcDbPolyline")
      (90 . 4) (70 . 1)
       (10 42.124 46.214) (10 43.876 46.214) (10 43.876 53.324) (10 42.124 53.324)
    ))
    (entmake '((0 . "LWPOLYLINE") (100 . "AcDbEntity") (8 . "0") (100 . "AcDbPolyline")
      (90 . 4) (70 . 1)
       (10 46.989 32.894) (10 48.502 32.012) (10 52.083 38.154) (10 50.569 39.036)
    ))
)

;; 单开: 外框 + 面板 + 1 按钮
(defun cc:GeomK1 ()
    (entmake '((0 . "LWPOLYLINE") (100 . "AcDbEntity") (8 . "0") (100 . "AcDbPolyline")
      (90 . 4) (70 . 1)
       (10 0 86) (10 86 86) (10 86 0) (10 0 0)
    ))
    (entmake '((0 . "LWPOLYLINE") (100 . "AcDbEntity") (8 . "0") (100 . "AcDbPolyline")
      (90 . 4) (70 . 1)
       (10 4 9.685) (10 82 9.682) (10 82 76.493) (10 4 76.495)
    ))
    (entmake '((0 . "LWPOLYLINE") (100 . "AcDbEntity") (8 . "0") (100 . "AcDbPolyline")
      (90 . 4) (70 . 1)
       (10 24.84 70.111) (10 61.16 70.111) (10 61.16 67.601) (10 24.84 67.601)
    ))
)

;; 双开: 外框 + 面板 + 2 按钮 + 分隔线
(defun cc:GeomK2 ()
    (entmake '((0 . "LWPOLYLINE") (100 . "AcDbEntity") (8 . "0") (100 . "AcDbPolyline")
      (90 . 4) (70 . 1)
       (10 0 86) (10 86 86) (10 86 0) (10 0 0)
    ))
    (entmake '((0 . "LWPOLYLINE") (100 . "AcDbEntity") (8 . "0") (100 . "AcDbPolyline")
      (90 . 4) (70 . 1)
       (10 3.974 9.685) (10 81.973 9.682) (10 81.973 76.493) (10 3.974 76.495)
    ))
    (entmake '((0 . "LWPOLYLINE") (100 . "AcDbEntity") (8 . "0") (100 . "AcDbPolyline")
      (90 . 4) (70 . 1)
       (10 14.381 67.601) (10 32.541 67.601) (10 32.541 70.111) (10 14.381 70.111)
    ))
    (entmake '((0 . "LINE") (100 . "AcDbEntity") (8 . "0") (100 . "AcDbLine") (10 42.973 76.495 0.0) (11 42.973 9.685 0.0)))
    (entmake '((0 . "LWPOLYLINE") (100 . "AcDbEntity") (8 . "0") (100 . "AcDbPolyline")
      (90 . 4) (70 . 1)
       (10 71.566 67.601) (10 53.406 67.601) (10 53.406 70.111) (10 71.566 70.111)
    ))
)

;; 三开: 外框 + 面板 + 3 按钮 + 分隔线
(defun cc:GeomK3 ()
    (entmake '((0 . "LWPOLYLINE") (100 . "AcDbEntity") (8 . "0") (100 . "AcDbPolyline")
      (90 . 4) (70 . 1)
       (10 0 86) (10 86 86) (10 86 0) (10 0 0)
    ))
    (entmake '((0 . "LWPOLYLINE") (100 . "AcDbEntity") (8 . "0") (100 . "AcDbPolyline")
      (90 . 4) (70 . 1)
       (10 3.974 9.685) (10 81.973 9.682) (10 81.973 76.493) (10 3.974 76.495)
    ))
    (entmake '((0 . "LWPOLYLINE") (100 . "AcDbEntity") (8 . "0") (100 . "AcDbPolyline")
      (90 . 4) (70 . 1)
       (10 7.893 67.601) (10 26.054 67.601) (10 26.054 70.111) (10 7.893 70.111)
    ))
    (entmake '((0 . "LINE") (100 . "AcDbEntity") (8 . "0") (100 . "AcDbLine") (10 29.974 76.495 0.0) (11 29.974 9.685 0.0)))
    (entmake '((0 . "LWPOLYLINE") (100 . "AcDbEntity") (8 . "0") (100 . "AcDbPolyline")
      (90 . 4) (70 . 1)
       (10 52.054 67.601) (10 33.893 67.601) (10 33.893 70.111) (10 52.054 70.111)
    ))
    (entmake '((0 . "LINE") (100 . "AcDbEntity") (8 . "0") (100 . "AcDbLine") (10 55.974 76.495 0.0) (11 55.974 9.685 0.0)))
    (entmake '((0 . "LWPOLYLINE") (100 . "AcDbEntity") (8 . "0") (100 . "AcDbPolyline")
      (90 . 4) (70 . 1)
       (10 78.053 67.601) (10 59.893 67.601) (10 59.893 70.111) (10 78.053 70.111)
    ))
)


;;; ---------------------------------------------------------------------
;;;  建块 / 插入
;;; ---------------------------------------------------------------------

;; 图形种类 -> 中文名
(defun cc:ModeName (m)
  (cond ((= m 5)  "五孔")
        ((= m 3)  "三孔")
        ((= m 11) "单开")
        ((= m 12) "双开")
        ((= m 13) "三开")
        (T        "?")))

;; 图形种类 -> 块名
(defun cc:BlkName (m)
  (cond ((= m 5)  "CC-86五孔插座")
        ((= m 3)  "CC-86三孔插座")
        ((= m 11) "CC-86单开开关")
        ((= m 12) "CC-86双开开关")
        ((= m 13) "CC-86三开开关")))

;; 建块: 已存在就直接用(不重复定义), 返回块名
;; 基点 = 0,0,0  ->  插入时以外框左下角为插入点
;; kind: 5=五孔 3=三孔 11=单开 12=双开 13=三开
(defun cc:Define (name kind)
  (if (not (tblsearch "BLOCK" name))
    (progn
      (entmake (list '(0 . "BLOCK")
                     '(100 . "AcDbEntity")
                     '(8 . "0")
                     '(100 . "AcDbBlockBegin")
                     (cons 2 name)
                     '(70 . 0)
                     '(10 0.0 0.0 0.0)
                     (cons 3 name)))
      (cond ((= kind 5)  (cc:Geom5))
            ((= kind 3)  (cc:Geom3))
            ((= kind 11) (cc:GeomK1))
            ((= kind 12) (cc:GeomK2))
            ((= kind 13) (cc:GeomK3)))
      (entmake '((0 . "ENDBLK")
                 (100 . "AcDbEntity")
                 (8 . "0")
                 (100 . "AcDbBlockEnd")))
    )
  )
  name
)

;; 插入: 直接 entmake 一个块参照, 不走 -INSERT 命令(无回显, 不闪屏)
;; 块参照放在当前图层上, 于是块内 0 层图元自动跟随当前图层颜色
(defun cc:Insert (blk pt)
  (entmake (list '(0 . "INSERT")
                 '(100 . "AcDbEntity")
                 (cons 8 (getvar "CLAYER"))
                 '(100 . "AcDbBlockReference")
                 (cons 2 blk)
                 (cons 10 pt)
                 '(41 . 1.0)
                 '(42 . 1.0)
                 '(43 . 1.0)
                 '(50 . 0.0)))
)


;;; ---------------------------------------------------------------------
;;;  CC --- 连续插入插座 / 开关
;;; ---------------------------------------------------------------------
(defun c:CC (/ mode pt k blk counts n)
  (setq mode 5)                                    ;; 默认五孔
  (setq counts (list (cons 5 0) (cons 3 0) (cons 11 0) (cons 12 0) (cons 13 0)))
  (while (progn
           (initget "S C V B")
           (setq pt
             (getpoint
               (strcat "\n[" (cc:ModeName mode)
                       "] 指定插入点(外框左下角) 或 [S 五孔/三孔   C 单开   V 双开   B 三开]"
                       " <回车 或 ESC 退出>: ")))
           (cond
             ;; S: 五孔 <-> 三孔 来回切
             ((= pt "S") (setq mode (if (= mode 5) 3 5)) T)
             ;; C / V / B: 直接切到对应开关
             ((= pt "C") (setq mode 11) T)
             ((= pt "V") (setq mode 12) T)
             ((= pt "B") (setq mode 13) T)
             ;; 点: 插入当前图形(块按需创建)
             ((= (type pt) 'LIST)
              (setq blk (cc:Define (cc:BlkName mode) mode))
              (if (cc:Insert blk pt)
                (setq counts (subst (cons mode (1+ (cdr (assoc mode counts))))
                                    (assoc mode counts) counts))
                (princ "\n  插入失败。")
              )
              T)
             ;; 回车 / ESC -> 结束
             (T nil)
           )
         )
  )
  (setq n 0)
  (foreach k '(5 3 11 12 13)
    (setq n (+ n (cdr (assoc k counts)))))
  (if (= n 0)
    (princ "\n[CC] 未插入任何图块。")
    (progn
      (princ "\n[CC] 本次共插入:")
      (foreach k '(5 3 11 12 13)
        (if (> (cdr (assoc k counts)) 0)
          (princ (strcat " " (cc:ModeName k) " " (itoa (cdr (assoc k counts))) " 个;"))))
    )
  )
  (princ)
)


;;; ---------------------------------------------------------------------
(princ "\n插座/开关图块工具已加载:  CC = 连续插入 (五孔/三孔 S 切, 单开 C, 双开 V, 三开 B, ESC 退出)")
(princ)
